; topo.lsp
; 170320


; TODO: rewrite!!!

;;; funció que dibuixa un punt amb la 'y' que li indiquem i la 'x' del punt marcat
(defun c:sec (/ pnt ent nent lent txt len m din dig cot vcot pntc os)
  (setq pnt (getpoint "marca un punt de la secció: "))
  (terpri)
  (setq
    ent	(entsel
	  "designa text amb cota, retorn per introduir numericament: "
	)
  )
  (if (= ent nil)
    (setq vcot (getreal "entreu valor z d'aquest punt: "))
  )
  (if (/= ent nil)
    (progn
      (setq nent (car ent))
      (setq lent (entget nent))
    )
  )
  (if (or (= (cdr (assoc 0 lent)) "text")
	  (= (cdr (assoc 0 lent)) "mtext")
      )
    (progn
      (setq txt (cdr (assoc 1 lent)))
      (setq len (strlen txt))
      (setq m 1)
      (while (/= m len)
	(setq din m)
	(setq dig (substr txt m 1))
	(setq m (+ m 1))
	(if (wcmatch dig "#")
	  (setq m len)
	)
      )
      (setq cot (substr txt din len))
      (setq vcot (atof cot))
    )
  )
  (setq pntc (list (car pnt) vcot 0))
  (setq os (getvar "osmode"))
  (setvar "osmode" 0)
  (command "_point" pntc)
  (setvar "osmode" os)
)
;;; similar a l'anterior però en comptes d'un punt hi posa una fletxa i text cota
(defun c:zec (/	    pnt	  ent	nent  lent  txt	  len	m     din
	      dig   cot	  vcot	pntc  xf    p1f	  p2f	pt    textp
	      textn os
	     )
  (setq pnt (getpoint "marca un punt de la secció: "))
  (terpri)
  (setq
    ent	(entsel
	  "designa text amb cota, retorn per introduir numericament: "
	)
  )
  (if (= ent nil)
    (setq vcot (getreal "entreu valor z d'aquest punt: "))
  )
  (if (/= ent nil)
    (progn
      (setq nent (car ent))
      (setq lent (entget nent))
    )
  )
  (if (or (= (cdr (assoc 0 lent)) "text")
	  (= (cdr (assoc 0 lent)) "mtext")
      )
    (progn
      (setq txt (cdr (assoc 1 lent)))
      (setq len (strlen txt))
      (setq m 1)
      (while (/= m len)
	(setq din m)
	(setq dig (substr txt m 1))
	(setq m (+ m 1))
	(if (wcmatch dig "#")
	  (setq m len)
	)
      )
      (setq cot (substr txt din len))
      (setq vcot (atof cot))
    )
  )
  (setq pntc (list (car pnt) vcot 0))
  (setq xf (/ *dit* (/ (sin (/ pi 3)) (cos (/ pi 3)))))
  (setq p1f (list (+ (car pntc) xf) (+ (cadr pntc) *dit*) (caddr pntc)))
  (setq p2f (list (- (car pntc) xf) (+ (cadr pntc) *dit*) (caddr pntc)))
  (setq os (getvar "osmode"))
  (setvar "osmode" 0)
  (command "_pline" pntc p1f p2f "_c" "")
  (setq pt (list (car pntc) (+ (cadr pntc) (* *dit* 2)) (caddr pntc)))
  (setq textp (strcat "c.+" (rtos vcot 2 2)))
  (setq textn (strcat "c." (rtos vcot 2 2)))
  (if (= vcot 0)
    (command "_text" "_m" pt "" "c.%%p0.00")
  )
  (if (> vcot 0)
    (command "_text" "_m" pt "" textp)
  )
  (if (< vcot 0)
    (command "_text" "_m" pt "" textn)
  )
  (setvar "osmode" os)
)
;;; redefinició origens cotes topogràfiques
(defun c:otto (/ p1 z1 p0 os)
  (setq p1 (getpoint "designa un punt: "))
  (terpri)
  (setq z1 (getreal "entra cota topogràfica per aquest punt: "))
  (terpri)
  (if (> z1 0)
    (setq p0 (polar p1 (* 3 (/ pi 2)) z1))
  )
  (if (= z1 0)
    (setq p0 p1)
  )
  (if (< z1 0)
    (setq p0 (polar p1 (/ pi 2) z1))
  )
  (setq os (getvar "osmode"))
  (setvar "osmode" 0)
  (command "_ucs" "o" p0 "")
  (setvar "osmode" os)
)
;;;
(defun c:loto (/ z pz os)
  (setq z (getreal "entra cota per on passa la liña: "))
  (terpri)
  (setq pz (list 0 z 0))
  (setq os (getvar "osmode"))
  (setvar "osmode" 0)ott
  (command "_xline" "_h" pz "")
  (setvar "osmode" os)
)
;;; simbol de cota amb el valor d'un punt designat
(defun c:topo (/ pc vc xf p1f p2f pt textp textn os)
  (setq pc (getpoint "designa un punt: "))
  (terpri)
  (setq vc (cadr pc))
  (setq xf (/ *dit* (/ (sin (/ pi 3)) (cos (/ pi 3)))))
  (setq p1f (list (+ (car pc) xf) (+ (cadr pc) *dit*) (caddr pc)))
  (setq p2f (list (- (car pc) xf) (+ (cadr pc) *dit*) (caddr pc)))
  (setq os (getvar "osmode"))
  (setvar "osmode" 0)
  (command "_pline" pc p1f p2f "_c")
  (setq pt (list (car pc) (+ (cadr pc) (* *dit* 2)) (caddr pc)))
  (setq textp (strcat "cota +" (rtos vc 2 2) " m."))
  (setq textn (strcat "cota " (rtos vc 2 2) " m."))
  (if (= vc 0)
    (command "_text" "_m" pt "" "cota %%p0.00 m.")
  )
  (if (> vc 0)
    (command "_text" "_m" pt "" textp)
  )
  (if (< vc 0)
    (command "_text" "_m" pt "" textn)
  )
  (setvar "osmode" os)
)
;;; simbol de cota amb el valor d'un punt designat
(defun c:top (/ pc vc xf p1f p2f pt txt os)
  (setq pc (getpoint "designa un punt: "))
  (terpri)
  (setq vc (cadr pc))
  (setq xf (/ *dit* (/ (sin (/ pi 3)) (cos (/ pi 3)))))
  (setq p1f (list (+ (car pc) xf) (+ (cadr pc) *dit*) (caddr pc)))
  (setq p2f (list (- (car pc) xf) (+ (cadr pc) *dit*) (caddr pc)))
  (setq os (getvar "osmode"))
  (setvar "osmode" 0)
  (command "_pline" pc p1f p2f "_c")
  (setq pt (list (car pc) (+ (cadr pc) (* *dit* 2)) (caddr pc)))
  (setq txt (rtos vc 2 2))
  (setq txt (acet-str-replace "." "," txt))
  (command "_text" "_m" pt "" txt)
  (setvar "osmode" os)
)
; (defun c:top (/ pc vc xf p1f p2f pt textp textn os)
;   (setq pc (getpoint "designa un punt: "))
;   (terpri)
;   (setq vc (cadr pc))
;   (setq xf (/ *dit* (/ (sin (/ pi 3)) (cos (/ pi 3)))))
;   (setq p1f (list (+ (car pc) xf) (+ (cadr pc) *dit*) (caddr pc)))
;   (setq p2f (list (- (car pc) xf) (+ (cadr pc) *dit*) (caddr pc)))
;   (setq os (getvar "osmode"))
;   (setvar "osmode" 0)
;   (command "_pline" pc p1f p2f "_c" "")
;   (setq pt (list (car pc) (+ (cadr pc) (* *dit* 2)) (caddr pc)))
;   (setq textp (strcat (rtos vc 2 2)))
;   (setq textn (strcat (rtos vc 2 2)))
; ; (if (= vc 0)(command "_text" "_m" pt "" "c.%%p0.00")
;   (if (= vc 0)
;     (command "_text" "_m" pt "" "" "0.00")
;   )
;   (if (> vc 0)
;     (command "_text" "_m" pt "" "" textp)
;   )
;   (if (< vc 0)
;     (command "_text" "_m" pt "" "" textn)
;   )
;   (setvar "osmode" os)
; )
;;; origen cotes
(defun c:origen	(/ pn1 val pn0)
  (setq pn1 (getpoint "entreu primer punt: "))
  (terpri)
  (setq val (getreal "entreu valor de la cota per aquest punt: "))
  (terpri)
  (if (= val 0)
    (setq pn0 pn1)
  )
  (if (< val 0)
    (setq pn0 (polar pn1 (/ pi 2) (* -1 val)))
  )
  (if (> val 0)
    (setq pn0 (polar pn1 (* 3 (/ pi 2)) val))
  )
  (command "_ucs" "_o" pn0)
)



;
(prompt "topo.lsp successfully loaded!\n")
